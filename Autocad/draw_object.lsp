(defun C:DrawMyObject ()
  (command "_.UNDO" "Begin")
  (setvar "CMDECHO" 0)
  ;; --- Dynamic Layer Setup ---
  (if (not (tblsearch "LTYPE" "Continuous")) (command "_.-LINETYPE" "_L" "Continuous" "acad.lin" "" ""))(command "_.-LAYER" "_M" "Outline" "_C" "7" "" "_L" "Continuous" "" "")(if (not (tblsearch "LTYPE" "CENTER")) (command "_.-LINETYPE" "_L" "CENTER" "acad.lin" "" ""))(command "_.-LAYER" "_M" "Centerline" "_C" "1" "" "_L" "CENTER" "" "")(if (not (tblsearch "LTYPE" "Continuous")) (command "_.-LINETYPE" "_L" "Continuous" "acad.lin" "" ""))(command "_.-LAYER" "_M" "Dimensions" "_C" "5" "" "_L" "Continuous" "" "")(if (not (tblsearch "LTYPE" "Continuous")) (command "_.-LINETYPE" "_L" "Continuous" "acad.lin" "" ""))(command "_.-LAYER" "_M" "Annotations" "_C" "6" "" "_L" "Continuous" "" "")(command "_.-LAYER" "_M" "Parameter_Table" "_C" "7" "" "")
  ;; --- Dimension and System Variable Setup ---
  (setvar "LTSCALE" 5.0)
  (setvar "DIMTXT" 3.5)
  (setvar "DIMASZ" 2.5)
  (setvar "DIMCLRD" 5)
  (setvar "DIMCLRE" 5)
  (setvar "DIMCLRT" 5)
  (setvar "DIMDEC" 2)

;; =============================================================================
;; == Helper Annotation Function Definitions (Generated by Python)
;; =============================================================================
(defun dtr (a) (* pi (/ a 180.0)))
(defun draw-roughness-symbol (ins_pt text_val sym_size rotation / p1 p2 p3 p4 ang1 ang2 text_height text_pt) (setq text_height (* sym_size 0.4)) (setq ang1 (dtr (+ rotation 60.0))) (setq ang2 (dtr (+ rotation 120.0))) (setq p1 ins_pt) (setq p2 (polar p1 ang1 sym_size)) (setq p3 (polar p2 ang2 sym_size)) (setq p4 (polar p3 (dtr rotation) (* sym_size 1.5))) (command "_.-LAYER" "_S" "Annotations" "") (command "_.PLINE" p1 p2 p3 "") (command "_.LINE" p3 p4 "") (setq text_pt (polar p2 (dtr (+ rotation 90)) (* text_height 0.4))) (command "_.TEXT" "_J" "_BL" text_pt text_height rotation text_val) )
(defun draw-datum-symbol (attach_pt label_pt label / frame_size p1 p2) (setq frame_size (* 3.5 2.0)) (command "_.-LAYER" "_S" "Annotations" "") (command "_.LEADER" attach_pt label_pt "" "" "_N") (setq p1 (list (- (car label_pt) (/ frame_size 2.0)) (- (cadr label_pt) (/ frame_size 2.0)))) (setq p2 (list (+ (car label_pt) (/ frame_size 2.0)) (+ (cadr label_pt) (/ frame_size 2.0)))) (command "_.RECTANG" p1 p2) (command "_.TEXT" "_J" "_MC" label_pt 3.5 0 (strcat "-" label "-")) )
(defun draw-gdt-frame (attach_pt frame_loc gdt_sym tolerance datums leader_side / total_width current_x box_w box_h leader_start_pt) (setq box_w (* 3.5 2.5)) (setq box_h (* 3.5 2.0)) (setq current_x (car frame_loc)) (setq total_width (+ box_w (* box_w 2) (* (if datums (length datums) 0) box_w))) (command "_.-LAYER" "_S" "Annotations" "") (if (or (not leader_side) (= (strcase leader_side) "LEFT")) (setq leader_start_pt (list (car frame_loc) (+ (cadr frame_loc) (/ box_h 2.0)))) (setq leader_start_pt (list (+ (car frame_loc) total_width) (+ (cadr frame_loc) (/ box_h 2.0))))) (command "_.LEADER" attach_pt leader_start_pt "" "" "_N") (command "_.RECTANG" (list current_x (cadr frame_loc)) (list (+ current_x box_w) (+ (cadr frame_loc) box_h))) (command "_.TEXT" "_J" "_MC" (list (+ current_x (/ box_w 2.0)) (+ (cadr frame_loc) (/ box_h 2.0))) 3.5 0 gdt_sym) (setq current_x (+ current_x box_w)) (command "_.RECTANG" (list current_x (cadr frame_loc)) (list (+ current_x (* box_w 2)) (+ (cadr frame_loc) box_h))) (command "_.TEXT" "_J" "_MC" (list (+ current_x box_w) (+ (cadr frame_loc) (/ box_h 2.0))) 3.5 0 tolerance) (setq current_x (+ current_x (* box_w 2))) (if datums (foreach datum datums (command "_.RECTANG" (list current_x (cadr frame_loc)) (list (+ current_x box_w) (+ (cadr frame_loc) box_h))) (command "_.TEXT" "_J" "_MC" (list (+ current_x (/ box_w 2.0)) (+ (cadr frame_loc) (/ box_h 2.0))) 3.5 0 datum) (setq current_x (+ current_x box_w)))) )
(defun Draw-Parameter-Table (start_pt title data_list col_widths row_height text_height / num_rows total_height total_width header_height current_y p1 p2 p3 p4 text_mid_y row_data i col_div_x) (command "_.-LAYER" "_S" "Parameter_Table" "") (setq num_rows (length data_list)) (if (> num_rows 0) (progn (setq header_height (* row_height 1.5)) (setq total_height (+ header_height (* num_rows row_height))) (setq total_width (apply '+ col_widths)) (setq p1 start_pt) (setq p2 (list (+ (car p1) total_width) (cadr p1))) (setq p3 (list (+ (car p1) total_width) (- (cadr p1) total_height))) (setq p4 (list (car p1) (- (cadr p1) total_height))) (command "_.RECTANG" p1 p3) (command "_.LINE" (list (car p1) (- (cadr p1) header_height)) (list (car p2) (- (cadr p2) header_height)) "") (setq col_div_x (+ (car p1) (car col_widths))) (command "_.LINE" (list col_div_x (- (cadr p1) header_height)) (list col_div_x (cadr p3)) "") (setq text_mid_y (- (cadr p1) (/ header_height 2.0))) (command "_.TEXT" "_J" "_MC" (list (+ (car p1) (/ total_width 2.0)) text_mid_y) (* text_height 1.2) 0 title) (setq current_y (- (cadr p1) header_height)) (setq i 0) (foreach row_data data_list (setq text_mid_y (- current_y (/ row_height 2.0))) (command "_.TEXT" "_J" "_MC" (list (+ (car p1) (/ (car col_widths) 2.0)) text_mid_y) text_height 0 (car row_data)) (command "_.TEXT" "_J" "_MC" (list (+ col_div_x (/ (cadr col_widths) 2.0)) text_mid_y) text_height 0 (cadr row_data)) (setq current_y (- current_y row_height)) (setq i (1+ i)) (if (< i num_rows) (command "_.LINE" (list (car p1) current_y) (list (car p2) current_y) ""))) (princ))))
(defun Draw-Bom-Table (start_pt title data_list col_widths row_height text_height / num_rows total_height total_width header_height current_y p1 p2 p3 p4 text_mid_y row_data i col_count current_x col_idx col_width temp_widths width) (command "_.-LAYER" "_S" "Parameter_Table" "" "") (setq num_rows (length data_list)) (setq col_count (length col_widths)) (if (> num_rows 0) (progn (setq header_height (* row_height 1.5)) (setq total_height (+ header_height (* num_rows row_height))) (setq total_width (apply '+ col_widths)) (setq p1 start_pt) (setq p2 (list (+ (car p1) total_width) (cadr p1))) (setq p3 (list (+ (car p1) total_width) (- (cadr p1) total_height))) (setq p4 (list (car p1) (- (cadr p1) total_height))) (command "_.RECTANG" p1 p3) (command "_.LINE" (list (car p1) (- (cadr p1) header_height)) (list (car p2) (- (cadr p2) header_height)) "") (setq current_x (car p1)) (setq temp_widths col_widths) (while (setq width (car temp_widths)) (setq current_x (+ current_x width)) (setq temp_widths (cdr temp_widths)) (if temp_widths (command "_.LINE" (list current_x (cadr p1)) (list current_x (cadr p3)) ""))) (setq text_mid_y (- (cadr p1) (/ header_height 2.0))) (command "_.TEXT" "_J" "_MC" (list (+ (car p1) (/ total_width 2.0)) text_mid_y) (* text_height 1.2) 0 title) (setq current_y (- (cadr p1) header_height)) (setq i 0) (foreach row_data data_list (setq text_mid_y (- current_y (/ row_height 2.0))) (setq current_x (car p1)) (setq col_idx 0) (foreach item row_data (setq col_width (nth col_idx col_widths)) (command "_.TEXT" "_J" "_MC" (list (+ current_x (/ col_width 2.0)) text_mid_y) text_height 0 (vl-princ-to-string item)) (setq current_x (+ current_x col_width)) (setq col_idx (1+ col_idx))) (setq current_y (- current_y row_height)) (setq i (1+ i)) (if (< i num_rows) (command "_.LINE" (list (car p1) current_y) (list (car p2) current_y) ""))) (princ))) )
(defun Draw-Balloon (center_pt radius text_val text_height) (command "_.-LAYER" "_S" "Annotations" "") (command "_.CIRCLE" center_pt radius) (command "_.TEXT" "_J" "_MC" center_pt text_height 0 text_val))

  (command "_.-LAYER" "_S" "Outline" "")(command "_.RECTANG" "10.0,10.0" "90.0,110.0")(command "_.RECTANG" "150.0,10.0" "230.0,110.0")(command "_.CIRCLE" "50.0,210.0" "40.0")
  (command "_.-LAYER" "_S" "Centerline" "")(command "_.LINE" "50.0,0.0" "50.0,120.0" "")(command "_.LINE" "0.0,210.0" "100.0,210.0" "")(command "_.LINE" "50.0,160.0" "50.0,260.0" "")(command "_.LINE" "190.0,0.0" "190.0,120.0" "")(command "_.LINE" "0.0,60.0" "240.0,60.0" "")
  (command "_.-LAYER" "_S" "Dimensions" "")(command "_.DIMLINEAR" "10.0,10.0" "10.0,110.0" "_T" "<> ±0.2" "-40.0,60.0")(command "_.DIMLINEAR" "10.0,210.0" "90.0,210.0" "_T" "%%c<> h8" "50.0,270.0")
  ;; --- Advanced Annotations ---
  (draw-datum-symbol (list 50.0 10.0) (list 50.0 -10.0) "A")
  (draw-datum-symbol (list 150.0 60.0) (list 130.0 50.0) "B")
  (draw-gdt-frame (list 10.0 60.0) (list -30.0 56.5) "\\U+22A5" "0.05" (list "A") "RIGHT")
  (draw-gdt-frame (list 230.0 60.0) (list 250.0 56.5) "\\U+2225" "0.02" (list "B") "LEFT")
  (draw-roughness-symbol (list 230.0 60.0) "Ra 3.2" 5 90)
  (draw-roughness-symbol (list 50.0 110.0) "Ra 1.6" 5 0)

  ;; --- Draw Parameter Table ---
  (setq table_start_pt (list 290.0 100))
  (setq param_data (list (list "Radius" "40.0") (list "Height" "100.0") (list "Height Tolerance" " ±0.2") (list "Diameter Tolerance" " h8")))
  (Draw-Parameter-Table table_start_pt "Parameter List" param_data '(150 80) 15 3.5)

  (setvar "CMDECHO" 1)(command "_.ZOOM" "_E")(command "_.UNDO" "End")
  (princ "\nCylinder drawing completed!\n")(princ))
(princ "\nLISP file loaded. Type 'DrawMyObject' to run.")(princ)
